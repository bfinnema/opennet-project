module newSubCPE {

  namespace "http://example.com/newSubCPE";
  prefix newSubCPE;

  import ietf-inet-types {
    prefix inet;
  }
  import tailf-common {
    prefix tailf;
  }
  import tailf-ncs {
    prefix ncs;
  }

  description
    "OpenNET. Provisioning of a new customer in the CPE for test and service assurance purposes";

  revision 2020-05-11 {
    description
      "Updated to be able to handle sp_termination_type, which can be BNG (new) or Other.";
  }

  revision 2019-02-18 {
    description
      "Initial revision.";
  }

  list newSubCPE {
    description "This is an RFS skeleton service";

    key subscription_id;
    leaf subscription_id {
      tailf:info "Subscription ID = SP ID + Subscriber ID + Service ID";
      type string;
    }

    leaf device {
      tailf:info "CPE device";
      type leafref {
        path "/ncs:devices/ncs:device/ncs:name";
      }
    }

    uses ncs:service-data;
    ncs:servicepoint newSubCPE-servicepoint;

    leaf cpe_id {
      tailf:info "A virtual CPE used for the demo";
      type uint32 {
        range "1..20";
      }
    }
    leaf sp_termination_type {
      tailf:info "BNG or not?";
      type enumeration {
        enum BNG;
        enum Other;
      }
      default Other;
    }
    list vlans {
      key inner_vlan;
      description "List of the inner and outer VLAN's for a specific subscription";

      leaf inner_vlan {
        tailf:info "VLAN to be mapped";
        type uint32 {
          range "30..199";
        }
      }

      leaf outer_vlan {
        tailf:info "VLAN to map to";
        type uint32 {
          range "100..999";
        }
      }
    }
  }
}
