module newSubPOI_EV {

  namespace "http://example.com/newSubPOI_EV";
  prefix newSubPOI_EV;

  import ietf-inet-types {
    prefix inet;
  }
  import tailf-common {
    prefix tailf;
  }
  import tailf-ncs {
    prefix ncs;
  }

  description
    "OpenNET. Provisioning of a new customer in a PoI with EVPN-VPWS between POI and PE";

  revision 2020-04-04 {
    description
      "Initial revision.";
  }

  list newSubPOI_EV {
    description "This is an RFS skeleton service";

    key subscription_id;
    leaf subscription_id {
      tailf:info "Subscription ID = SP ID + Subscriber ID + Service ID";
      type string;
    }

    uses ncs:service-data;
    ncs:servicepoint newSubPOI_EV-servicepoint;

    leaf device {
      tailf:info "PoI Area";
      type leafref {
        path "/ncs:devices/ncs:device/ncs:name";
      }
      mandatory true;
    }
    leaf poi_interface {
      tailf:info "POI Interface towards SP. Example: 0/0/2/0";
      type string;
      mandatory true;
    }
    leaf sp_id {
      tailf:info "Service Provider. Example: ISPT";
      type string;
      mandatory true;
    }
    leaf QoS_Out {
      tailf:info "Upstream QoS profile. Example: 220M_TDC_UNI_OUT";
      type string;
      default "220M_TDC_UNI_OUT";
    }
    leaf QoS_In {
      tailf:info "Downstream QoS profile. Example: 220M_TDC_UNI_IN";
      type string;
      default "220M_TDC_UNI_IN";
    }
    leaf original_s_vlan {
      tailf:info "Provider VLAN (100-999). If the subscriber is moved, it is the original one that must be used here. Example: 501";
      type uint32 {
        range "100..999";
      }
      mandatory true;
    }
    leaf evi {
      tailf:info "EVI (100-999). Example: 540";
      type uint32 {
        range "100..999";
      }
      mandatory true;
    }
    leaf target {
      tailf:info "EVPN EVI Target (1-99). Example: 40";
      type uint32 {
        range "1..99";
      }
      mandatory true;
    }
    leaf source {
      tailf:info "EVPN EVI source (1-99). Example: 40";
      type uint32 {
        range "1..99";
      }
      mandatory true;
    }
    container c_vlans {
      list c_vlan {
        key "old_c_vlan_id";
        leaf old_c_vlan_id {
          tailf:info "Original outer Subscriber VLAN (100-999)";
          type uint32 {
            range "100..999";
          }
        }
      }
    }
  }
}
