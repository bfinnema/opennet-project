module newSubSP {

  namespace "http://example.com/newSubSP";
  prefix newSubSP;

  import ietf-inet-types {
    prefix inet;
  }
  import tailf-common {
    prefix tailf;
  }
  import tailf-ncs {
    prefix ncs;
  }

  description
    "OpenNET. Provisioning of a new customer in a SP router to be able to test end-to-end connectivity";

  revision 2020-04-04 {
    description
      "Initial revision.";
  }

  list newSubSP {
    description "This is an RFS skeleton service";

    key subscription_id;
    leaf subscription_id {
      tailf:info "Subscription ID = SP ID + Subscriber ID + Service ID";
      type string;
    }

    uses ncs:service-data;
    ncs:servicepoint newSubSP-servicepoint;

    leaf device {
      tailf:info "PoI Area";
      type leafref {
        path "/ncs:devices/ncs:device/ncs:name";
      }
      mandatory true;
    }

    leaf cpe_id {
      tailf:info "A virtual CPE used for the demo. Example: 1";
      type uint32 {
        range "1..20";
      }
      mandatory true;
    }
    leaf remote_interface {
      tailf:info "SP Remote POI interface. Example: 0/0/2/3";
      type string;
      mandatory true;
    }
    leaf sp_id {
      tailf:info "Service Provider. Example: ISPT";
      /* type leafref {
        path "/open-net:open-net-access/open-net:inventory/open-net:sps/open-net:sp/open-net:sp_id";
      } */
      type string;
      mandatory true;
    }
    leaf original_s_vlan {
      tailf:info "Provider VLAN (100-999) for a moved subscriber. Example: 501";
      type uint32 {
        range "100..999";
      }
      mandatory true;
    }

    container c_vlans {
      list c_vlan {
        key "c_vlan_id";
        leaf c_vlan_id {
          tailf:info "Subscriber VLAN (100-999)";
          type uint32 {
            range "100..999";
          }
        }
        leaf old_c_vlan_id {
          tailf:info "Original outer Subscriber VLAN (100-999). If the subscriber is not moved, it is the same as the Subscriber VLAN (c_vlan)";
          type uint32 {
            range "100..999";
          }
        }
      }
    }
  }
}
