module newSubPE_EV {

  namespace "http://example.com/newSubPE_EV";
  prefix newSubPE_EV;

  import ietf-inet-types {
    prefix inet;
  }
  import tailf-common {
    prefix tailf;
  }
  import tailf-ncs {
    prefix ncs;
  }

  description
    "OpenNET. Provisioning of a new customer in a PE using EVPN VPWS between PE and POI";

  revision 2020-04-04 {
    description
      "Initial revision.";
  }

  list newSubPE_EV {
    description "This is an RFS skeleton service";

    key subscription_id;
    leaf subscription_id {
      tailf:info "Subscription ID = SP ID + Subscriber ID + Service ID";
      type string;
    }

    uses ncs:service-data;
    ncs:servicepoint newSubPE_EV-servicepoint;

    leaf device {
      tailf:info "PE Router to serve this Subscriber";
      type leafref {
        path "/ncs:devices/ncs:device/ncs:name";
      }
    }

    leaf pe_interface {
      tailf:info "Interface designation. Example: 0/0/0/0.520";
      type string;
    }

    leaf sp_id {
      tailf:info "Service Provider. Example: ISPT";
      type string;
    }

    leaf evi {
      tailf:info "EVI (100-999). Example: 540";
      type uint32 {
        range "100..999";
      }
      mandatory true;
    }
    leaf target {
      tailf:info "EVPN EVI Target (1-99). Example: 40";
      type uint32 {
        range "1..99";
      }
      mandatory true;
    }
    leaf source {
      tailf:info "EVPN EVI source (1-99). Example: 40";
      type uint32 {
        range "1..99";
      }
      mandatory true;
    }

    container vlans {
      list vlan {
        key "vlan_id";
        leaf vlan_id {
          tailf:info "Subscriber VLAN (100-999)";
          type uint32 {
            range "100..999";
          }
        }
      }
    }
  }
}
